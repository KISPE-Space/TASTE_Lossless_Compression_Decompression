Uartotherend-Datamodel DEFINITIONS ::=
BEGIN
--  This file was generated automatically by OpenGEODE
IMPORTS
   MyInteger, CompressorDataBuffer, CompressorState FROM CG-TEST-2-DATAVIEW
   T-Int32, T-UInt32, T-Int8, T-UInt8, T-Boolean, T-Null-Record, T-Runtime-Error FROM TASTE-BasicTypes
   PID-Range, PID FROM System-Dataview;

Uartotherend-States ::= ENUMERATED {wait}

Uartotherend-Context ::= SEQUENCE {
   state Uartotherend-States,
   init-done BOOLEAN,
   sender PID,
   offspring PID
}

Uartotherend-T-Runtime-Error-Selection ::= ENUMERATED {noerror-present(1), encodeerror-present(2), decodeerror-present(3)}
END
